module example {
    yang-version 1.1;
    namespace "urn:opendaylight:params:xml:ns:yang:example";
    prefix "example";

    revision "2018-05-17" {
        description "Initial revision of example model";
    }

    container example-container {
        description "A container for example properties";

        list example-list {
            key "name";
            leaf name {
                type string;
            }
            leaf value {
                type string;
            }
        }
    }

    rpc hello-world {
        input {
            leaf name {
                type string;
            }
        }
        output {
            leaf greeting {
                type string;
            }
        }
    }

    rpc add-name {
        input {
            leaf name {
                type string;
                description "The name to add";
            }
            leaf value {
                type string;
                description "The value associated with the name";
            }
        }
        output {
            leaf result {
                type string;
                description "Result of the add-name operation";
            }
        }
    }

    rpc get-name {
        input {
            leaf name {
                type string;
                description "The name to get";
            }
        }
        output {
            leaf value {
                type string;
                description "The value associated with the name";
            }
        }
    }
}
